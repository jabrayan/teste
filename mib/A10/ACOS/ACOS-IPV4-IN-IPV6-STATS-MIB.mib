ACOS-IPV4-IN-IPV6-STATS-MIB DEFINITIONS ::= BEGIN
	IMPORTS
		DisplayString, PhysAddress
		FROM SNMPv2-TC
	InetAddressType
		FROM INET-ADDRESS-MIB
	acosRootStats
		FROM A10-AX-MIB
	MODULE-IDENTITY, OBJECT-TYPE, Counter32, Integer32, Counter64, OBJECT-IDENTITY, NOTIFICATION-TYPE
		FROM SNMPv2-SMI;
		acosIpv4InIpv6 MODULE-IDENTITY
				LAST-UPDATED	"200705071327Z"
				ORGANIZATION	"A10 Networks, Inc."
				CONTACT-INFO	"Address: A10 Networks, Inc.
							  3 West Pumeria Dr.
							  San Jose, CA 95131
						 Phone:   +1-888-822-7210 (USA/Canada)
						          +1-408-325-8676 (International)
						 E-mail:  support@A10Networks.com"

				DESCRIPTION	 "Ipv4InIpv6 OID for ACOS"
				::=  {  acosRootStats 98  }

acosIpv4InIpv6Frag                  OBJECT IDENTIFIER ::= { acosIpv4InIpv6 1 }
acosIpv4InIpv6FragS                 OBJECT IDENTIFIER ::= { acosIpv4InIpv6Frag 1 }

		ipv4InIpv6SessionInserted OBJECT-TYPE
		SYNTAX  CounterBasedGauge64 
		MAX-ACCESS read-only 
		STATUS current
		DESCRIPTION  "Session Inserted" 
		::={ acosIpv4InIpv6FragS 1 } 

		ipv4InIpv6SessionExpired OBJECT-TYPE
		SYNTAX  CounterBasedGauge64 
		MAX-ACCESS read-only 
		STATUS current
		DESCRIPTION  "Session Expired" 
		::={ acosIpv4InIpv6FragS 2 } 

		ipv4InIpv6IcmpRcv OBJECT-TYPE
		SYNTAX  CounterBasedGauge64 
		MAX-ACCESS read-only 
		STATUS current
		DESCRIPTION  "ICMP Received" 
		::={ acosIpv4InIpv6FragS 3 } 

		ipv4InIpv6Icmpv6Rcv OBJECT-TYPE
		SYNTAX  CounterBasedGauge64 
		MAX-ACCESS read-only 
		STATUS current
		DESCRIPTION  "ICMPv6 Received" 
		::={ acosIpv4InIpv6FragS 4 } 

		ipv4InIpv6UdpRcv OBJECT-TYPE
		SYNTAX  CounterBasedGauge64 
		MAX-ACCESS read-only 
		STATUS current
		DESCRIPTION  "UDP Received" 
		::={ acosIpv4InIpv6FragS 5 } 

		ipv4InIpv6TcpRcv OBJECT-TYPE
		SYNTAX  CounterBasedGauge64 
		MAX-ACCESS read-only 
		STATUS current
		DESCRIPTION  "TCP Received" 
		::={ acosIpv4InIpv6FragS 6 } 

		ipv4InIpv6IpipRcv OBJECT-TYPE
		SYNTAX  CounterBasedGauge64 
		MAX-ACCESS read-only 
		STATUS current
		DESCRIPTION  "IP-in-IP Received" 
		::={ acosIpv4InIpv6FragS 7 } 

		ipv4InIpv6Ipv6ipRcv OBJECT-TYPE
		SYNTAX  CounterBasedGauge64 
		MAX-ACCESS read-only 
		STATUS current
		DESCRIPTION  "IPv6-in-IP Received" 
		::={ acosIpv4InIpv6FragS 8 } 

		ipv4InIpv6OtherRcv OBJECT-TYPE
		SYNTAX  CounterBasedGauge64 
		MAX-ACCESS read-only 
		STATUS current
		DESCRIPTION  "Other Received" 
		::={ acosIpv4InIpv6FragS 9 } 

		ipv4InIpv6IcmpDropped OBJECT-TYPE
		SYNTAX  CounterBasedGauge64 
		MAX-ACCESS read-only 
		STATUS current
		DESCRIPTION  "ICMP Dropped" 
		::={ acosIpv4InIpv6FragS 10 } 

		ipv4InIpv6Icmpv6Dropped OBJECT-TYPE
		SYNTAX  CounterBasedGauge64 
		MAX-ACCESS read-only 
		STATUS current
		DESCRIPTION  "ICMPv6 Dropped" 
		::={ acosIpv4InIpv6FragS 11 } 

		ipv4InIpv6UdpDropped OBJECT-TYPE
		SYNTAX  CounterBasedGauge64 
		MAX-ACCESS read-only 
		STATUS current
		DESCRIPTION  "UDP Dropped" 
		::={ acosIpv4InIpv6FragS 12 } 

		ipv4InIpv6TcpDropped OBJECT-TYPE
		SYNTAX  CounterBasedGauge64 
		MAX-ACCESS read-only 
		STATUS current
		DESCRIPTION  "TCP Dropped" 
		::={ acosIpv4InIpv6FragS 13 } 

		ipv4InIpv6IpipDropped OBJECT-TYPE
		SYNTAX  CounterBasedGauge64 
		MAX-ACCESS read-only 
		STATUS current
		DESCRIPTION  "IP-in-IP Dropped" 
		::={ acosIpv4InIpv6FragS 14 } 

		ipv4InIpv6Ipv6ipDropped OBJECT-TYPE
		SYNTAX  CounterBasedGauge64 
		MAX-ACCESS read-only 
		STATUS current
		DESCRIPTION  "IPv6-in-IP Dropped" 
		::={ acosIpv4InIpv6FragS 15 } 

		ipv4InIpv6OtherDropped OBJECT-TYPE
		SYNTAX  CounterBasedGauge64 
		MAX-ACCESS read-only 
		STATUS current
		DESCRIPTION  "Other Dropped" 
		::={ acosIpv4InIpv6FragS 16 } 

		ipv4InIpv6OverlapError OBJECT-TYPE
		SYNTAX  CounterBasedGauge64 
		MAX-ACCESS read-only 
		STATUS current
		DESCRIPTION  "Overlapping Fragment Dropped" 
		::={ acosIpv4InIpv6FragS 17 } 

		ipv4InIpv6BadIpLen OBJECT-TYPE
		SYNTAX  CounterBasedGauge64 
		MAX-ACCESS read-only 
		STATUS current
		DESCRIPTION  "Bad IP Length" 
		::={ acosIpv4InIpv6FragS 18 } 

		ipv4InIpv6TooSmall OBJECT-TYPE
		SYNTAX  CounterBasedGauge64 
		MAX-ACCESS read-only 
		STATUS current
		DESCRIPTION  "Fragment Too Small Drop" 
		::={ acosIpv4InIpv6FragS 19 } 

		ipv4InIpv6FirstTcpTooSmall OBJECT-TYPE
		SYNTAX  CounterBasedGauge64 
		MAX-ACCESS read-only 
		STATUS current
		DESCRIPTION  "First TCP Fragment Too Small Drop" 
		::={ acosIpv4InIpv6FragS 20 } 

		ipv4InIpv6FirstL4TooSmall OBJECT-TYPE
		SYNTAX  CounterBasedGauge64 
		MAX-ACCESS read-only 
		STATUS current
		DESCRIPTION  "First L4 Fragment Too Small Drop" 
		::={ acosIpv4InIpv6FragS 21 } 

		ipv4InIpv6TotalSessionsExceeded OBJECT-TYPE
		SYNTAX  CounterBasedGauge64 
		MAX-ACCESS read-only 
		STATUS current
		DESCRIPTION  "Total Sessions Exceeded Drop" 
		::={ acosIpv4InIpv6FragS 22 } 

		ipv4InIpv6NoSessionMemory OBJECT-TYPE
		SYNTAX  CounterBasedGauge64 
		MAX-ACCESS read-only 
		STATUS current
		DESCRIPTION  "Out of Session Memory" 
		::={ acosIpv4InIpv6FragS 23 } 

		ipv4InIpv6FastAgingSet OBJECT-TYPE
		SYNTAX  CounterBasedGauge64 
		MAX-ACCESS read-only 
		STATUS current
		DESCRIPTION  "Fragmentation Fast Aging Set" 
		::={ acosIpv4InIpv6FragS 24 } 

		ipv4InIpv6FastAgingUnset OBJECT-TYPE
		SYNTAX  CounterBasedGauge64 
		MAX-ACCESS read-only 
		STATUS current
		DESCRIPTION  "Fragmentation Fast Aging Unset" 
		::={ acosIpv4InIpv6FragS 25 } 

		ipv4InIpv6FragmentQueueSuccess OBJECT-TYPE
		SYNTAX  CounterBasedGauge64 
		MAX-ACCESS read-only 
		STATUS current
		DESCRIPTION  "Fragment Queue Success" 
		::={ acosIpv4InIpv6FragS 26 } 

		ipv4InIpv6Unaligned OBJECT-TYPE
		SYNTAX  CounterBasedGauge64 
		MAX-ACCESS read-only 
		STATUS current
		DESCRIPTION  "Payload Length Unaligned" 
		::={ acosIpv4InIpv6FragS 27 } 

		ipv4InIpv6ExceededLen OBJECT-TYPE
		SYNTAX  CounterBasedGauge64 
		MAX-ACCESS read-only 
		STATUS current
		DESCRIPTION  "Payload Length Out of Bounds" 
		::={ acosIpv4InIpv6FragS 28 } 

		ipv4InIpv6DuplicateFirstFrag OBJECT-TYPE
		SYNTAX  CounterBasedGauge64 
		MAX-ACCESS read-only 
		STATUS current
		DESCRIPTION  "Duplicate First Fragment" 
		::={ acosIpv4InIpv6FragS 29 } 

		ipv4InIpv6DuplicateLastFrag OBJECT-TYPE
		SYNTAX  CounterBasedGauge64 
		MAX-ACCESS read-only 
		STATUS current
		DESCRIPTION  "Duplicate Last Fragment" 
		::={ acosIpv4InIpv6FragS 30 } 

		ipv4InIpv6TotalFragmentsExceeded OBJECT-TYPE
		SYNTAX  CounterBasedGauge64 
		MAX-ACCESS read-only 
		STATUS current
		DESCRIPTION  "Total Queued Fragments Exceeded" 
		::={ acosIpv4InIpv6FragS 31 } 

		ipv4InIpv6FragmentQueueFailure OBJECT-TYPE
		SYNTAX  CounterBasedGauge64 
		MAX-ACCESS read-only 
		STATUS current
		DESCRIPTION  "Fragment Queue Failure" 
		::={ acosIpv4InIpv6FragS 32 } 

		ipv4InIpv6ReassemblySuccess OBJECT-TYPE
		SYNTAX  CounterBasedGauge64 
		MAX-ACCESS read-only 
		STATUS current
		DESCRIPTION  "Fragment Reassembly Success" 
		::={ acosIpv4InIpv6FragS 33 } 

		ipv4InIpv6MaxLenExceeded OBJECT-TYPE
		SYNTAX  CounterBasedGauge64 
		MAX-ACCESS read-only 
		STATUS current
		DESCRIPTION  "Fragment Max Data Length Exceeded" 
		::={ acosIpv4InIpv6FragS 34 } 

		ipv4InIpv6ReassemblyFailure OBJECT-TYPE
		SYNTAX  CounterBasedGauge64 
		MAX-ACCESS read-only 
		STATUS current
		DESCRIPTION  "Fragment Reassembly Failure" 
		::={ acosIpv4InIpv6FragS 35 } 

		ipv4InIpv6PolicyDrop OBJECT-TYPE
		SYNTAX  CounterBasedGauge64 
		MAX-ACCESS read-only 
		STATUS current
		DESCRIPTION  "MTU Exceeded Policy Drop" 
		::={ acosIpv4InIpv6FragS 36 } 

		ipv4InIpv6ErrorDrop OBJECT-TYPE
		SYNTAX  CounterBasedGauge64 
		MAX-ACCESS read-only 
		STATUS current
		DESCRIPTION  "Fragment Processing Drop" 
		::={ acosIpv4InIpv6FragS 37 } 

		highCpuThreshold OBJECT-TYPE
		SYNTAX  CounterBasedGauge64 
		MAX-ACCESS read-only 
		STATUS current
		DESCRIPTION  "High CPU Threshold Reached" 
		::={ acosIpv4InIpv6FragS 38 } 

		lowCpuThreshold OBJECT-TYPE
		SYNTAX  CounterBasedGauge64 
		MAX-ACCESS read-only 
		STATUS current
		DESCRIPTION  "Low CPU Threshold Reached" 
		::={ acosIpv4InIpv6FragS 39 } 

		cpuThresholdDrop OBJECT-TYPE
		SYNTAX  CounterBasedGauge64 
		MAX-ACCESS read-only 
		STATUS current
		DESCRIPTION  "High CPU Drop" 
		::={ acosIpv4InIpv6FragS 40 } 

		ipdEntryDrop OBJECT-TYPE
		SYNTAX  CounterBasedGauge64 
		MAX-ACCESS read-only 
		STATUS current
		DESCRIPTION  "DDoS Protection Drop" 
		::={ acosIpv4InIpv6FragS 41 } 

		ipv4InIpv6MaxPackets OBJECT-TYPE
		SYNTAX  CounterBasedGauge64 
		MAX-ACCESS read-only 
		STATUS current
		DESCRIPTION  "Too Many Packets Per Reassembly Drop" 
		::={ acosIpv4InIpv6FragS 42 } 

		ipv4InIpv6SessionPacketsExceeded OBJECT-TYPE
		SYNTAX  CounterBasedGauge64 
		MAX-ACCESS read-only 
		STATUS current
		DESCRIPTION  "Session Max Packets Exceeded" 
		::={ acosIpv4InIpv6FragS 43 } 

		fragSessionCount OBJECT-TYPE
		SYNTAX  CounterBasedGauge64 
		MAX-ACCESS read-only 
		STATUS current
		DESCRIPTION  "Fragmentation Session Count" 
		::={ acosIpv4InIpv6FragS 44 } 

		ipv4InIpv6SctpRcv OBJECT-TYPE
		SYNTAX  CounterBasedGauge64 
		MAX-ACCESS read-only 
		STATUS current
		DESCRIPTION  "SCTP Received" 
		::={ acosIpv4InIpv6FragS 45 } 

		ipv4InIpv6SctpDropped OBJECT-TYPE
		SYNTAX  CounterBasedGauge64 
		MAX-ACCESS read-only 
		STATUS current
		DESCRIPTION  "SCTP Dropped" 
		::={ acosIpv4InIpv6FragS 46 } 

END

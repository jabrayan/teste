ACOS-VISIBILITY-STATS-MIB DEFINITIONS ::= BEGIN
	IMPORTS
		DisplayString, PhysAddress
		FROM SNMPv2-TC
	InetAddressType
		FROM INET-ADDRESS-MIB
	acosRootStats
		FROM A10-AX-MIB
	MODULE-IDENTITY, OBJECT-TYPE, Counter32, Integer32, Counter64, OBJECT-IDENTITY, NOTIFICATION-TYPE
		FROM SNMPv2-SMI;
		acosVisibility MODULE-IDENTITY
				LAST-UPDATED	"200705071327Z"
				ORGANIZATION	"A10 Networks, Inc."
				CONTACT-INFO	"Address: A10 Networks, Inc.
							  3 West Pumeria Dr.
							  San Jose, CA 95131
						 Phone:   +1-888-822-7210 (USA/Canada)
						          +1-408-325-8676 (International)
						 E-mail:  support@A10Networks.com"

				DESCRIPTION	 "Visibility OID for ACOS"
				::=  {  acosRootStats 169  }

acosVisibility                      OBJECT IDENTIFIER ::= { acosRootStats 169 }
acosVisibilityS                     OBJECT IDENTIFIER ::= { acosVisibility 1 }

		monEntityLimitExceed OBJECT-TYPE
		SYNTAX  CounterBasedGauge64 
		MAX-ACCESS read-only 
		STATUS current
		DESCRIPTION  "Total monitor entity limit exceed failures" 
		::={ acosVisibilityS 1 } 

		haEntityCreateSent OBJECT-TYPE
		SYNTAX  CounterBasedGauge64 
		MAX-ACCESS read-only 
		STATUS current
		DESCRIPTION  "Total montior entity HA create messages sent" 
		::={ acosVisibilityS 2 } 

		haEntityDeleteSent OBJECT-TYPE
		SYNTAX  CounterBasedGauge64 
		MAX-ACCESS read-only 
		STATUS current
		DESCRIPTION  "Total montior entity HA delete messages sent" 
		::={ acosVisibilityS 3 } 

		haEntityAnomalyOnSent OBJECT-TYPE
		SYNTAX  CounterBasedGauge64 
		MAX-ACCESS read-only 
		STATUS current
		DESCRIPTION  "Total anomaly on HA messages sent" 
		::={ acosVisibilityS 4 } 

		haEntityAnomalyOffSent OBJECT-TYPE
		SYNTAX  CounterBasedGauge64 
		MAX-ACCESS read-only 
		STATUS current
		DESCRIPTION  "Total anomaly off HA messages sent" 
		::={ acosVisibilityS 5 } 

		haEntityPeriodicSyncSent OBJECT-TYPE
		SYNTAX  CounterBasedGauge64 
		MAX-ACCESS read-only 
		STATUS current
		DESCRIPTION  "Total monitor entity periodic sync messages sent" 
		::={ acosVisibilityS 6 } 

		outOfMemoryAllocFailures OBJECT-TYPE
		SYNTAX  CounterBasedGauge64 
		MAX-ACCESS read-only 
		STATUS current
		DESCRIPTION  "Out of memory allocation failures" 
		::={ acosVisibilityS 7 } 

		lwMonEntityCreated OBJECT-TYPE
		SYNTAX  CounterBasedGauge64 
		MAX-ACCESS read-only 
		STATUS current
		DESCRIPTION  "Total Light-weight entities created" 
		::={ acosVisibilityS 8 } 

		lwMonEntityDeleted OBJECT-TYPE
		SYNTAX  CounterBasedGauge64 
		MAX-ACCESS read-only 
		STATUS current
		DESCRIPTION  "Total Light-weight entities deleted" 
		::={ acosVisibilityS 9 } 

		lwMonEntityLimitExceed OBJECT-TYPE
		SYNTAX  CounterBasedGauge64 
		MAX-ACCESS read-only 
		STATUS current
		DESCRIPTION  "Light weight limit exceeded errors" 
		::={ acosVisibilityS 10 } 

		lwOutOfMemoryAllocFailures OBJECT-TYPE
		SYNTAX  CounterBasedGauge64 
		MAX-ACCESS read-only 
		STATUS current
		DESCRIPTION  "Light Weight Out-of-memory allocation failures" 
		::={ acosVisibilityS 11 } 

		monEntityRrdFileTimestampErr OBJECT-TYPE
		SYNTAX  CounterBasedGauge64 
		MAX-ACCESS read-only 
		STATUS current
		DESCRIPTION  "Total monitor entity rrd file timestamp errors" 
		::={ acosVisibilityS 12 } 

		monEntityRrdUpdateErr OBJECT-TYPE
		SYNTAX  CounterBasedGauge64 
		MAX-ACCESS read-only 
		STATUS current
		DESCRIPTION  "Total monitor entity rrd update error" 
		::={ acosVisibilityS 13 } 

		monEntityRrdLastUpdateFetchFailedErr OBJECT-TYPE
		SYNTAX  CounterBasedGauge64 
		MAX-ACCESS read-only 
		STATUS current
		DESCRIPTION  "Total monitor entity rrd last update fetch failed error" 
		::={ acosVisibilityS 14 } 

		monEntityRrdTuneErr OBJECT-TYPE
		SYNTAX  CounterBasedGauge64 
		MAX-ACCESS read-only 
		STATUS current
		DESCRIPTION  "Total monitor entity rrd tune error" 
		::={ acosVisibilityS 15 } 

		monEntityRrdOutOfMemoryErr OBJECT-TYPE
		SYNTAX  CounterBasedGauge64 
		MAX-ACCESS read-only 
		STATUS current
		DESCRIPTION  "Total monitor entity rrd load failed, out of memory error" 
		::={ acosVisibilityS 16 } 

		monEntityRrdFileCreateErr OBJECT-TYPE
		SYNTAX  CounterBasedGauge64 
		MAX-ACCESS read-only 
		STATUS current
		DESCRIPTION  "Total monitor entity rrd file create error" 
		::={ acosVisibilityS 17 } 

acosVisibilityReporting             OBJECT IDENTIFIER ::= { acosVisibility 4 }
acosVisibilityReportingS            OBJECT IDENTIFIER ::= { acosVisibilityReporting 1 }

		logTransmitFailure OBJECT-TYPE
		SYNTAX  CounterBasedGauge64 
		MAX-ACCESS read-only 
		STATUS current
		DESCRIPTION  "Total log transmit failures" 
		::={ acosVisibilityReportingS 1 } 

		bufferAllocFailure OBJECT-TYPE
		SYNTAX  CounterBasedGauge64 
		MAX-ACCESS read-only 
		STATUS current
		DESCRIPTION  "Total reporting buffer allocation failures" 
		::={ acosVisibilityReportingS 2 } 

		notifJobsInQueue OBJECT-TYPE
		SYNTAX  CounterBasedGauge64 
		MAX-ACCESS read-only 
		STATUS current
		DESCRIPTION  "Total notification jobs in queue" 
		::={ acosVisibilityReportingS 3 } 

		enqueueFail OBJECT-TYPE
		SYNTAX  CounterBasedGauge64 
		MAX-ACCESS read-only 
		STATUS current
		DESCRIPTION  "Total enqueue jobs failed" 
		::={ acosVisibilityReportingS 4 } 

		enqueuePass OBJECT-TYPE
		SYNTAX  CounterBasedGauge64 
		MAX-ACCESS read-only 
		STATUS current
		DESCRIPTION  "Total enqueue jobs passed" 
		::={ acosVisibilityReportingS 5 } 

		dequeued OBJECT-TYPE
		SYNTAX  CounterBasedGauge64 
		MAX-ACCESS read-only 
		STATUS current
		DESCRIPTION  "Total jobs dequeued" 
		::={ acosVisibilityReportingS 6 } 

acosVisibilityReportingTemplate     OBJECT IDENTIFIER ::= { acosVisibilityReporting 2 }
acosVisibilityFlowCollector         OBJECT IDENTIFIER ::= { acosVisibility 6 }
acosVisibilityFlowCollectorSflow    OBJECT IDENTIFIER ::= { acosVisibilityFlowCollector 1 }
acosVisibilityFlowCollectorSflowS   OBJECT IDENTIFIER ::= { acosVisibilityFlowCollectorSflow 1 }

		pktsReceived OBJECT-TYPE
		SYNTAX  CounterBasedGauge64 
		MAX-ACCESS read-only 
		STATUS current
		DESCRIPTION  "Total sflow pkts received" 
		::={ acosVisibilityFlowCollectorSflowS 1 } 

		fragDropped OBJECT-TYPE
		SYNTAX  CounterBasedGauge64 
		MAX-ACCESS read-only 
		STATUS current
		DESCRIPTION  "Total sflow fragment packets droppped" 
		::={ acosVisibilityFlowCollectorSflowS 2 } 

		agentNotFound OBJECT-TYPE
		SYNTAX  CounterBasedGauge64 
		MAX-ACCESS read-only 
		STATUS current
		DESCRIPTION  "sflow pkts from not configured agents" 
		::={ acosVisibilityFlowCollectorSflowS 3 } 

		versionNotSupported OBJECT-TYPE
		SYNTAX  CounterBasedGauge64 
		MAX-ACCESS read-only 
		STATUS current
		DESCRIPTION  "sflow version not supported" 
		::={ acosVisibilityFlowCollectorSflowS 4 } 

		unknownDir OBJECT-TYPE
		SYNTAX  CounterBasedGauge64 
		MAX-ACCESS read-only 
		STATUS current
		DESCRIPTION  "sflow sample direction is unknown" 
		::={ acosVisibilityFlowCollectorSflowS 5 } 

acosVisibilityFlowCollectorNetflow  OBJECT IDENTIFIER ::= { acosVisibilityFlowCollector 1 }
acosVisibilityFlowCollectorNetflowS OBJECT IDENTIFIER ::= { acosVisibilityFlowCollectorNetflow 1 }

		pktsRcvd OBJECT-TYPE
		SYNTAX  CounterBasedGauge64 
		MAX-ACCESS read-only 
		STATUS current
		DESCRIPTION  "Total nflow packets received" 
		::={ acosVisibilityFlowCollectorNetflowS 1 } 

		v9TemplatesCreated OBJECT-TYPE
		SYNTAX  CounterBasedGauge64 
		MAX-ACCESS read-only 
		STATUS current
		DESCRIPTION  "Total v9 templates created" 
		::={ acosVisibilityFlowCollectorNetflowS 2 } 

		v9TemplatesDeleted OBJECT-TYPE
		SYNTAX  CounterBasedGauge64 
		MAX-ACCESS read-only 
		STATUS current
		DESCRIPTION  "Total v9 templates deleted" 
		::={ acosVisibilityFlowCollectorNetflowS 3 } 

		v10TemplatesCreated OBJECT-TYPE
		SYNTAX  CounterBasedGauge64 
		MAX-ACCESS read-only 
		STATUS current
		DESCRIPTION  "Total v10(IPFIX) templates created" 
		::={ acosVisibilityFlowCollectorNetflowS 4 } 

		v10TemplatesDeleted OBJECT-TYPE
		SYNTAX  CounterBasedGauge64 
		MAX-ACCESS read-only 
		STATUS current
		DESCRIPTION  "Total v10(IPFIX) templates deleted" 
		::={ acosVisibilityFlowCollectorNetflowS 5 } 

		templateDropExceeded OBJECT-TYPE
		SYNTAX  CounterBasedGauge64 
		MAX-ACCESS read-only 
		STATUS current
		DESCRIPTION  "Total templates dropped because of maximum limit" 
		::={ acosVisibilityFlowCollectorNetflowS 6 } 

		templateDropOutOfMemory OBJECT-TYPE
		SYNTAX  CounterBasedGauge64 
		MAX-ACCESS read-only 
		STATUS current
		DESCRIPTION  "Total templates dropped becuase of out of memory" 
		::={ acosVisibilityFlowCollectorNetflowS 7 } 

		fragDropped OBJECT-TYPE
		SYNTAX  CounterBasedGauge64 
		MAX-ACCESS read-only 
		STATUS current
		DESCRIPTION  "Total nflow fragment packets droppped" 
		::={ acosVisibilityFlowCollectorNetflowS 8 } 

		agentNotFound OBJECT-TYPE
		SYNTAX  CounterBasedGauge64 
		MAX-ACCESS read-only 
		STATUS current
		DESCRIPTION  "nflow pkts from not configured agents" 
		::={ acosVisibilityFlowCollectorNetflowS 9 } 

		versionNotSupported OBJECT-TYPE
		SYNTAX  CounterBasedGauge64 
		MAX-ACCESS read-only 
		STATUS current
		DESCRIPTION  "nflow version not supported" 
		::={ acosVisibilityFlowCollectorNetflowS 10 } 

		unknownDir OBJECT-TYPE
		SYNTAX  CounterBasedGauge64 
		MAX-ACCESS read-only 
		STATUS current
		DESCRIPTION  "nflow sample direction is unknown" 
		::={ acosVisibilityFlowCollectorNetflowS 11 } 

END

ACOS-VRRP-A-STATS-MIB DEFINITIONS ::= BEGIN
	IMPORTS
		DisplayString, PhysAddress
		FROM SNMPv2-TC
	InetAddressType
		FROM INET-ADDRESS-MIB
	acosRootStats
		FROM A10-AX-MIB
	MODULE-IDENTITY, OBJECT-TYPE, Counter32, Integer32, Counter64, OBJECT-IDENTITY, NOTIFICATION-TYPE
		FROM SNMPv2-SMI;
		acosVrrpA MODULE-IDENTITY
				LAST-UPDATED	"200705071327Z"
				ORGANIZATION	"A10 Networks, Inc."
				CONTACT-INFO	"Address: A10 Networks, Inc.
							  3 West Pumeria Dr.
							  San Jose, CA 95131
						 Phone:   +1-888-822-7210 (USA/Canada)
						          +1-408-325-8676 (International)
						 E-mail:  support@A10Networks.com"

				DESCRIPTION	 "VrrpA OID for ACOS"
				::=  {  acosRootStats 13  }

acosVrrpAState                      OBJECT IDENTIFIER ::= { acosVrrpA 1 }
acosVrrpAStateS                     OBJECT IDENTIFIER ::= { acosVrrpAState 1 }

		syncPktTxCounter OBJECT-TYPE
		SYNTAX  CounterBasedGauge64 
		MAX-ACCESS read-only 
		STATUS current
		DESCRIPTION  "Conn Sync Sent counter" 
		::={ acosVrrpAStateS 1 } 

		syncPktRcvCounter OBJECT-TYPE
		SYNTAX  CounterBasedGauge64 
		MAX-ACCESS read-only 
		STATUS current
		DESCRIPTION  "Conn Sync Received counter" 
		::={ acosVrrpAStateS 2 } 

		syncRxCreateCounter OBJECT-TYPE
		SYNTAX  CounterBasedGauge64 
		MAX-ACCESS read-only 
		STATUS current
		DESCRIPTION  "Conn Sync Create Session Received counter" 
		::={ acosVrrpAStateS 3 } 

		syncRxDelCounter OBJECT-TYPE
		SYNTAX  CounterBasedGauge64 
		MAX-ACCESS read-only 
		STATUS current
		DESCRIPTION  "Conn Sync Del Session Received counter" 
		::={ acosVrrpAStateS 4 } 

		syncRxUpdateAgeCounter OBJECT-TYPE
		SYNTAX  CounterBasedGauge64 
		MAX-ACCESS read-only 
		STATUS current
		DESCRIPTION  "Conn Sync Update Age Received counter" 
		::={ acosVrrpAStateS 5 } 

		syncTxCreateCounter OBJECT-TYPE
		SYNTAX  CounterBasedGauge64 
		MAX-ACCESS read-only 
		STATUS current
		DESCRIPTION  "Conn Sync Create Session Sent counter" 
		::={ acosVrrpAStateS 6 } 

		syncTxDelCounter OBJECT-TYPE
		SYNTAX  CounterBasedGauge64 
		MAX-ACCESS read-only 
		STATUS current
		DESCRIPTION  "Conn Sync Del Session Sent counter" 
		::={ acosVrrpAStateS 7 } 

		syncTxUpdateAgeCounter OBJECT-TYPE
		SYNTAX  CounterBasedGauge64 
		MAX-ACCESS read-only 
		STATUS current
		DESCRIPTION  "Conn Sync Update Age Sent counter" 
		::={ acosVrrpAStateS 8 } 

		syncRxPersistCreateCounter OBJECT-TYPE
		SYNTAX  CounterBasedGauge64 
		MAX-ACCESS read-only 
		STATUS current
		DESCRIPTION  "Conn Sync Create Persist Session Pkts Received counter" 
		::={ acosVrrpAStateS 9 } 

		syncRxPersistDelCounter OBJECT-TYPE
		SYNTAX  CounterBasedGauge64 
		MAX-ACCESS read-only 
		STATUS current
		DESCRIPTION  "Conn Sync Delete Persist Session Pkts Received counter" 
		::={ acosVrrpAStateS 10 } 

		syncRxPersistUpdateAgeCounter OBJECT-TYPE
		SYNTAX  CounterBasedGauge64 
		MAX-ACCESS read-only 
		STATUS current
		DESCRIPTION  "Conn Sync Update Persist Age Pkts Received counter" 
		::={ acosVrrpAStateS 11 } 

		syncTxPersistCreateCounter OBJECT-TYPE
		SYNTAX  CounterBasedGauge64 
		MAX-ACCESS read-only 
		STATUS current
		DESCRIPTION  "Conn Sync Create Persist Session Pkts Sent counter" 
		::={ acosVrrpAStateS 12 } 

		syncTxPersistDelCounter OBJECT-TYPE
		SYNTAX  CounterBasedGauge64 
		MAX-ACCESS read-only 
		STATUS current
		DESCRIPTION  "Conn Sync Delete Persist Session Pkts Sent counter" 
		::={ acosVrrpAStateS 13 } 

		syncTxPersistUpdateAgeCounter OBJECT-TYPE
		SYNTAX  CounterBasedGauge64 
		MAX-ACCESS read-only 
		STATUS current
		DESCRIPTION  "Conn Sync Update Persist Age Pkts Sent counter" 
		::={ acosVrrpAStateS 14 } 

		queryPktTxCounter OBJECT-TYPE
		SYNTAX  CounterBasedGauge64 
		MAX-ACCESS read-only 
		STATUS current
		DESCRIPTION  "Conn Query sent counter" 
		::={ acosVrrpAStateS 15 } 

		queryPktRcvCounter OBJECT-TYPE
		SYNTAX  CounterBasedGauge64 
		MAX-ACCESS read-only 
		STATUS current
		DESCRIPTION  "Conn Query Received counter" 
		::={ acosVrrpAStateS 16 } 

		syncTxSmpRadiusTableCounter OBJECT-TYPE
		SYNTAX  CounterBasedGauge64 
		MAX-ACCESS read-only 
		STATUS current
		DESCRIPTION  "Conn Sync Update LSN RADIUS Sent counter" 
		::={ acosVrrpAStateS 17 } 

		syncRxSmpRadiusTableCounter OBJECT-TYPE
		SYNTAX  CounterBasedGauge64 
		MAX-ACCESS read-only 
		STATUS current
		DESCRIPTION  "Conn Sync Update LSN RADIUS Received counter" 
		::={ acosVrrpAStateS 18 } 

		queryTxMaxPacked OBJECT-TYPE
		SYNTAX  CounterBasedGauge64 
		MAX-ACCESS read-only 
		STATUS current
		DESCRIPTION  "Max Query Msg Per Packet" 
		::={ acosVrrpAStateS 19 } 

		queryTxMinPacked OBJECT-TYPE
		SYNTAX  CounterBasedGauge64 
		MAX-ACCESS read-only 
		STATUS current
		DESCRIPTION  "Min Query Msg Per Packet" 
		::={ acosVrrpAStateS 20 } 

		queryPktInvalidIdxCounter OBJECT-TYPE
		SYNTAX  CounterBasedGauge64 
		MAX-ACCESS read-only 
		STATUS current
		DESCRIPTION  "Conn Query Invalid Interface" 
		::={ acosVrrpAStateS 21 } 

		queryTxGetBuffFailed OBJECT-TYPE
		SYNTAX  CounterBasedGauge64 
		MAX-ACCESS read-only 
		STATUS current
		DESCRIPTION  "Conn Query Get Buff Failure" 
		::={ acosVrrpAStateS 22 } 

		queryRxZeroInfoCounter OBJECT-TYPE
		SYNTAX  CounterBasedGauge64 
		MAX-ACCESS read-only 
		STATUS current
		DESCRIPTION  "Conn Query Packet Empty" 
		::={ acosVrrpAStateS 23 } 

		queryRxFullInfoCounter OBJECT-TYPE
		SYNTAX  CounterBasedGauge64 
		MAX-ACCESS read-only 
		STATUS current
		DESCRIPTION  "Conn Query Packet Full" 
		::={ acosVrrpAStateS 24 } 

		queryRxUnkCounter OBJECT-TYPE
		SYNTAX  CounterBasedGauge64 
		MAX-ACCESS read-only 
		STATUS current
		DESCRIPTION  "Conn Query Unknown Type" 
		::={ acosVrrpAStateS 25 } 

		syncPktInvalidIdxCounter OBJECT-TYPE
		SYNTAX  CounterBasedGauge64 
		MAX-ACCESS read-only 
		STATUS current
		DESCRIPTION  "Conn Sync Invalid Interface" 
		::={ acosVrrpAStateS 26 } 

		syncTxGetBuffFailed OBJECT-TYPE
		SYNTAX  CounterBasedGauge64 
		MAX-ACCESS read-only 
		STATUS current
		DESCRIPTION  "Conn Sync Get Buff Failure" 
		::={ acosVrrpAStateS 27 } 

		syncTxTotalInfoCounter OBJECT-TYPE
		SYNTAX  CounterBasedGauge64 
		MAX-ACCESS read-only 
		STATUS current
		DESCRIPTION  "Conn Sync Total Info Pkts Sent counter" 
		::={ acosVrrpAStateS 28 } 

		syncTxCreateExtBitCounter OBJECT-TYPE
		SYNTAX  CounterBasedGauge64 
		MAX-ACCESS read-only 
		STATUS current
		DESCRIPTION  "Conn Sync Create with Ext Sent counter" 
		::={ acosVrrpAStateS 29 } 

		syncTxUpdateSeqnosCounter OBJECT-TYPE
		SYNTAX  CounterBasedGauge64 
		MAX-ACCESS read-only 
		STATUS current
		DESCRIPTION  "Conn Sync Update Seq Num Sent counter" 
		::={ acosVrrpAStateS 30 } 

		syncTxMinPacked OBJECT-TYPE
		SYNTAX  CounterBasedGauge64 
		MAX-ACCESS read-only 
		STATUS current
		DESCRIPTION  "Max Sync Msg Per Packet" 
		::={ acosVrrpAStateS 31 } 

		syncTxMaxPacked OBJECT-TYPE
		SYNTAX  CounterBasedGauge64 
		MAX-ACCESS read-only 
		STATUS current
		DESCRIPTION  "Min Sync Msg Per Packet" 
		::={ acosVrrpAStateS 32 } 

		syncRxLenInvalid OBJECT-TYPE
		SYNTAX  CounterBasedGauge64 
		MAX-ACCESS read-only 
		STATUS current
		DESCRIPTION  "Conn Sync Length Invalid" 
		::={ acosVrrpAStateS 33 } 

		syncPersistRxLenInvalid OBJECT-TYPE
		SYNTAX  CounterBasedGauge64 
		MAX-ACCESS read-only 
		STATUS current
		DESCRIPTION  "Persist Conn Sync Length Invalid" 
		::={ acosVrrpAStateS 34 } 

		syncPersistRxProtoNotSupported OBJECT-TYPE
		SYNTAX  CounterBasedGauge64 
		MAX-ACCESS read-only 
		STATUS current
		DESCRIPTION  "Persist Conn Sync Protocol Invalid" 
		::={ acosVrrpAStateS 35 } 

		syncPersistRxTypeInvalid OBJECT-TYPE
		SYNTAX  CounterBasedGauge64 
		MAX-ACCESS read-only 
		STATUS current
		DESCRIPTION  "Persist Conn Sync Type Invalid" 
		::={ acosVrrpAStateS 36 } 

		syncPersistRxCannotProcessMandatory OBJECT-TYPE
		SYNTAX  CounterBasedGauge64 
		MAX-ACCESS read-only 
		STATUS current
		DESCRIPTION  "Persist Conn Sync Process Mandatory Invalid" 
		::={ acosVrrpAStateS 37 } 

		syncPersistRxExtBitProcessError OBJECT-TYPE
		SYNTAX  CounterBasedGauge64 
		MAX-ACCESS read-only 
		STATUS current
		DESCRIPTION  "Persist Conn Sync Proc Ext Bit Failure" 
		::={ acosVrrpAStateS 38 } 

		syncPersistRxNoSuchVport OBJECT-TYPE
		SYNTAX  CounterBasedGauge64 
		MAX-ACCESS read-only 
		STATUS current
		DESCRIPTION  "Persist Conn Sync Virt Port Not Found" 
		::={ acosVrrpAStateS 39 } 

		syncPersistRxVporttypeNotSupported OBJECT-TYPE
		SYNTAX  CounterBasedGauge64 
		MAX-ACCESS read-only 
		STATUS current
		DESCRIPTION  "Persist Conn Sync Virt Port Type Invalid" 
		::={ acosVrrpAStateS 40 } 

		syncPersistRxNoSuchRport OBJECT-TYPE
		SYNTAX  CounterBasedGauge64 
		MAX-ACCESS read-only 
		STATUS current
		DESCRIPTION  "Persist Conn Sync Real Port Not Found" 
		::={ acosVrrpAStateS 41 } 

		syncPersistRxNoSuchSgGroup OBJECT-TYPE
		SYNTAX  CounterBasedGauge64 
		MAX-ACCESS read-only 
		STATUS current
		DESCRIPTION  "Persist Conn Sync No Service Group Found" 
		::={ acosVrrpAStateS 42 } 

		syncPersistRxNoSgGroupInfo OBJECT-TYPE
		SYNTAX  CounterBasedGauge64 
		MAX-ACCESS read-only 
		STATUS current
		DESCRIPTION  "Persist Conn Sync No Service Group Info Found" 
		::={ acosVrrpAStateS 43 } 

		syncPersistRxConnGetFailed OBJECT-TYPE
		SYNTAX  CounterBasedGauge64 
		MAX-ACCESS read-only 
		STATUS current
		DESCRIPTION  "Persist Conn Sync Get Conn Failure" 
		::={ acosVrrpAStateS 44 } 

		syncRxNoSuchVport OBJECT-TYPE
		SYNTAX  CounterBasedGauge64 
		MAX-ACCESS read-only 
		STATUS current
		DESCRIPTION  "Conn Sync Virt Port Not Found" 
		::={ acosVrrpAStateS 45 } 

		syncRxNoSuchRport OBJECT-TYPE
		SYNTAX  CounterBasedGauge64 
		MAX-ACCESS read-only 
		STATUS current
		DESCRIPTION  "Conn Sync Real Port Not Found" 
		::={ acosVrrpAStateS 46 } 

		syncRxCannotProcessMandatory OBJECT-TYPE
		SYNTAX  CounterBasedGauge64 
		MAX-ACCESS read-only 
		STATUS current
		DESCRIPTION  "Conn Sync Process Mandatory Invalid" 
		::={ acosVrrpAStateS 47 } 

		syncRxExtBitProcessError OBJECT-TYPE
		SYNTAX  CounterBasedGauge64 
		MAX-ACCESS read-only 
		STATUS current
		DESCRIPTION  "Conn Sync Proc Ext Bit Failure" 
		::={ acosVrrpAStateS 48 } 

		syncRxCreateExtBitCounter OBJECT-TYPE
		SYNTAX  CounterBasedGauge64 
		MAX-ACCESS read-only 
		STATUS current
		DESCRIPTION  "Conn Sync Create with Ext Received counter" 
		::={ acosVrrpAStateS 49 } 

		syncRxConnExists OBJECT-TYPE
		SYNTAX  CounterBasedGauge64 
		MAX-ACCESS read-only 
		STATUS current
		DESCRIPTION  "Conn Sync Create Conn Exists" 
		::={ acosVrrpAStateS 50 } 

		syncRxConnGetFailed OBJECT-TYPE
		SYNTAX  CounterBasedGauge64 
		MAX-ACCESS read-only 
		STATUS current
		DESCRIPTION  "Conn Sync Get Conn Failure" 
		::={ acosVrrpAStateS 51 } 

		syncRxProtoNotSupported OBJECT-TYPE
		SYNTAX  CounterBasedGauge64 
		MAX-ACCESS read-only 
		STATUS current
		DESCRIPTION  "Conn Sync Protocol Invalid" 
		::={ acosVrrpAStateS 52 } 

		syncRxNoDstForVportInline OBJECT-TYPE
		SYNTAX  CounterBasedGauge64 
		MAX-ACCESS read-only 
		STATUS current
		DESCRIPTION  "Conn Sync 'dst' not found for vport inline" 
		::={ acosVrrpAStateS 53 } 

		syncRxNoSuchNatPool OBJECT-TYPE
		SYNTAX  CounterBasedGauge64 
		MAX-ACCESS read-only 
		STATUS current
		DESCRIPTION  "Conn Sync NAT Pool Error" 
		::={ acosVrrpAStateS 54 } 

		syncRxNoSuchSgNode OBJECT-TYPE
		SYNTAX  CounterBasedGauge64 
		MAX-ACCESS read-only 
		STATUS current
		DESCRIPTION  "Conn Sync no SG node found" 
		::={ acosVrrpAStateS 55 } 

		syncRxDelNoSuchSession OBJECT-TYPE
		SYNTAX  CounterBasedGauge64 
		MAX-ACCESS read-only 
		STATUS current
		DESCRIPTION  "Conn Sync Del Conn not Found" 
		::={ acosVrrpAStateS 56 } 

		syncRxTypeInvalid OBJECT-TYPE
		SYNTAX  CounterBasedGauge64 
		MAX-ACCESS read-only 
		STATUS current
		DESCRIPTION  "Conn Sync Type Invalid" 
		::={ acosVrrpAStateS 57 } 

		syncRxZeroInfoCounter OBJECT-TYPE
		SYNTAX  CounterBasedGauge64 
		MAX-ACCESS read-only 
		STATUS current
		DESCRIPTION  "Conn Sync Packet Empty" 
		::={ acosVrrpAStateS 58 } 

		syncRxDcmsgCounter OBJECT-TYPE
		SYNTAX  CounterBasedGauge64 
		MAX-ACCESS read-only 
		STATUS current
		DESCRIPTION  "Conn Sync forward CPU" 
		::={ acosVrrpAStateS 59 } 

		syncRxTotalInfoCounter OBJECT-TYPE
		SYNTAX  CounterBasedGauge64 
		MAX-ACCESS read-only 
		STATUS current
		DESCRIPTION  "Conn Sync Total Info Pkts Received counter" 
		::={ acosVrrpAStateS 60 } 

		syncRxUpdateSeqnosCounter OBJECT-TYPE
		SYNTAX  CounterBasedGauge64 
		MAX-ACCESS read-only 
		STATUS current
		DESCRIPTION  "Conn Sync Update Seq Num Received counter" 
		::={ acosVrrpAStateS 61 } 

		syncRxUnkCounter OBJECT-TYPE
		SYNTAX  CounterBasedGauge64 
		MAX-ACCESS read-only 
		STATUS current
		DESCRIPTION  "Conn Sync Unknown Type" 
		::={ acosVrrpAStateS 62 } 

		syncRxApptypeNotSupported OBJECT-TYPE
		SYNTAX  CounterBasedGauge64 
		MAX-ACCESS read-only 
		STATUS current
		DESCRIPTION  "Conn Sync App Type Invalid" 
		::={ acosVrrpAStateS 63 } 

		syncQueryDcmsgCounter OBJECT-TYPE
		SYNTAX  CounterBasedGauge64 
		MAX-ACCESS read-only 
		STATUS current
		DESCRIPTION  "Conn Sync query forward CPU" 
		::={ acosVrrpAStateS 64 } 

		syncGetBuffFailedRt OBJECT-TYPE
		SYNTAX  CounterBasedGauge64 
		MAX-ACCESS read-only 
		STATUS current
		DESCRIPTION  "Conn Sync Get Buff Failure No Route" 
		::={ acosVrrpAStateS 65 } 

		syncGetBuffFailedPort OBJECT-TYPE
		SYNTAX  CounterBasedGauge64 
		MAX-ACCESS read-only 
		STATUS current
		DESCRIPTION  "Conn Sync Get Buff Failure Wrong Port" 
		::={ acosVrrpAStateS 66 } 

		syncRxLsnCreateSby OBJECT-TYPE
		SYNTAX  CounterBasedGauge64 
		MAX-ACCESS read-only 
		STATUS current
		DESCRIPTION  "Conn Sync LSN Create Standby" 
		::={ acosVrrpAStateS 67 } 

		syncRxNatCreateSby OBJECT-TYPE
		SYNTAX  CounterBasedGauge64 
		MAX-ACCESS read-only 
		STATUS current
		DESCRIPTION  "Conn Sync NAT Create Standby" 
		::={ acosVrrpAStateS 68 } 

		syncRxNatAllocSby OBJECT-TYPE
		SYNTAX  CounterBasedGauge64 
		MAX-ACCESS read-only 
		STATUS current
		DESCRIPTION  "Conn Sync NAT Alloc Standby" 
		::={ acosVrrpAStateS 69 } 

		syncRxInsertTuple OBJECT-TYPE
		SYNTAX  CounterBasedGauge64 
		MAX-ACCESS read-only 
		STATUS current
		DESCRIPTION  "Conn Sync Insert Tuple" 
		::={ acosVrrpAStateS 70 } 

		syncRxSfw OBJECT-TYPE
		SYNTAX  CounterBasedGauge64 
		MAX-ACCESS read-only 
		STATUS current
		DESCRIPTION  "Conn Sync SFW" 
		::={ acosVrrpAStateS 71 } 

		syncRxCreateStaticSby OBJECT-TYPE
		SYNTAX  CounterBasedGauge64 
		MAX-ACCESS read-only 
		STATUS current
		DESCRIPTION  "Conn Sync Create Static Standby" 
		::={ acosVrrpAStateS 72 } 

		syncRxExtPptp OBJECT-TYPE
		SYNTAX  CounterBasedGauge64 
		MAX-ACCESS read-only 
		STATUS current
		DESCRIPTION  "Conn Sync Ext PPTP" 
		::={ acosVrrpAStateS 73 } 

		syncRxExtRtsp OBJECT-TYPE
		SYNTAX  CounterBasedGauge64 
		MAX-ACCESS read-only 
		STATUS current
		DESCRIPTION  "Conn Sync Ext RTSP" 
		::={ acosVrrpAStateS 74 } 

		syncRxReserveHa OBJECT-TYPE
		SYNTAX  CounterBasedGauge64 
		MAX-ACCESS read-only 
		STATUS current
		DESCRIPTION  "Conn Sync Reserve HA Conn" 
		::={ acosVrrpAStateS 75 } 

		syncRxSeqDeltas OBJECT-TYPE
		SYNTAX  CounterBasedGauge64 
		MAX-ACCESS read-only 
		STATUS current
		DESCRIPTION  "Conn Sync Seq Deltas Failure" 
		::={ acosVrrpAStateS 76 } 

		syncRxFtpControl OBJECT-TYPE
		SYNTAX  CounterBasedGauge64 
		MAX-ACCESS read-only 
		STATUS current
		DESCRIPTION  "Conn Sync FTP Control Failure" 
		::={ acosVrrpAStateS 77 } 

		syncRxExtLsnAcl OBJECT-TYPE
		SYNTAX  CounterBasedGauge64 
		MAX-ACCESS read-only 
		STATUS current
		DESCRIPTION  "Conn Sync LSN ACL Failure" 
		::={ acosVrrpAStateS 78 } 

		syncRxExtLsnAcIdleTimeout OBJECT-TYPE
		SYNTAX  CounterBasedGauge64 
		MAX-ACCESS read-only 
		STATUS current
		DESCRIPTION  "Conn Sync LSN ACL Idle Timeout Failure" 
		::={ acosVrrpAStateS 79 } 

		syncRxExtSipAlg OBJECT-TYPE
		SYNTAX  CounterBasedGauge64 
		MAX-ACCESS read-only 
		STATUS current
		DESCRIPTION  "Conn Sync SIP TCP ALG Failure" 
		::={ acosVrrpAStateS 80 } 

		syncRxExtH323Alg OBJECT-TYPE
		SYNTAX  CounterBasedGauge64 
		MAX-ACCESS read-only 
		STATUS current
		DESCRIPTION  "Conn Sync H323 TCP ALG Failure" 
		::={ acosVrrpAStateS 81 } 

		syncRxExtNatMac OBJECT-TYPE
		SYNTAX  CounterBasedGauge64 
		MAX-ACCESS read-only 
		STATUS current
		DESCRIPTION  "Conn Sync NAT MAC Failure" 
		::={ acosVrrpAStateS 82 } 

		syncTxLsnFullcone OBJECT-TYPE
		SYNTAX  CounterBasedGauge64 
		MAX-ACCESS read-only 
		STATUS current
		DESCRIPTION  "Conn Sync Update LSN Fullcone Sent counter" 
		::={ acosVrrpAStateS 83 } 

		syncRxLsnFullcone OBJECT-TYPE
		SYNTAX  CounterBasedGauge64 
		MAX-ACCESS read-only 
		STATUS current
		DESCRIPTION  "Conn Sync Update LSN Fullcone Received counter" 
		::={ acosVrrpAStateS 84 } 

		syncErrLsnFullcone OBJECT-TYPE
		SYNTAX  CounterBasedGauge64 
		MAX-ACCESS read-only 
		STATUS current
		DESCRIPTION  "Conn Sync LSN Fullcone Failure" 
		::={ acosVrrpAStateS 85 } 

		syncTxUpdateSctpConnAddr OBJECT-TYPE
		SYNTAX  CounterBasedGauge64 
		MAX-ACCESS read-only 
		STATUS current
		DESCRIPTION  "Update SCTP Addresses Sent" 
		::={ acosVrrpAStateS 86 } 

		syncRxUpdateSctpConnAddr OBJECT-TYPE
		SYNTAX  CounterBasedGauge64 
		MAX-ACCESS read-only 
		STATUS current
		DESCRIPTION  "Update SCTP Addresses Received" 
		::={ acosVrrpAStateS 87 } 

		syncRxExtNatAlgTcpInfo OBJECT-TYPE
		SYNTAX  CounterBasedGauge64 
		MAX-ACCESS read-only 
		STATUS current
		DESCRIPTION  "Conn Sync NAT ALG TCP Information" 
		::={ acosVrrpAStateS 88 } 

		syncRxExtDcfwRuleId OBJECT-TYPE
		SYNTAX  CounterBasedGauge64 
		MAX-ACCESS read-only 
		STATUS current
		DESCRIPTION  "Conn Sync FIREWALL session rule ID information Failure" 
		::={ acosVrrpAStateS 89 } 

		syncRxExtDcfwLog OBJECT-TYPE
		SYNTAX  CounterBasedGauge64 
		MAX-ACCESS read-only 
		STATUS current
		DESCRIPTION  "Conn Sync FIREWALL session logging information Failure" 
		::={ acosVrrpAStateS 90 } 

		syncRxEstabCounter OBJECT-TYPE
		SYNTAX  CounterBasedGauge64 
		MAX-ACCESS read-only 
		STATUS current
		DESCRIPTION  "Conn Sync rcv established state" 
		::={ acosVrrpAStateS 91 } 

		syncTxEstabCounter OBJECT-TYPE
		SYNTAX  CounterBasedGauge64 
		MAX-ACCESS read-only 
		STATUS current
		DESCRIPTION  "Conn Sync send established state" 
		::={ acosVrrpAStateS 92 } 

		syncRxZoneFailureCounter OBJECT-TYPE
		SYNTAX  CounterBasedGauge64 
		MAX-ACCESS read-only 
		STATUS current
		DESCRIPTION  "Conn Sync Zone Failure" 
		::={ acosVrrpAStateS 93 } 

		syncRxExtFwHttpLogging OBJECT-TYPE
		SYNTAX  CounterBasedGauge64 
		MAX-ACCESS read-only 
		STATUS current
		DESCRIPTION  "FW HTTP Logging Sync Failures" 
		::={ acosVrrpAStateS 94 } 

		syncRxExtDcfwRuleIdleTimeout OBJECT-TYPE
		SYNTAX  CounterBasedGauge64 
		MAX-ACCESS read-only 
		STATUS current
		DESCRIPTION  "Conn Sync FIREWALL session rule idle timeout information Failure" 
		::={ acosVrrpAStateS 95 } 

		syncRxExtFwGtpInfo OBJECT-TYPE
		SYNTAX  CounterBasedGauge64 
		MAX-ACCESS read-only 
		STATUS current
		DESCRIPTION  "FW GTP Info Received" 
		::={ acosVrrpAStateS 96 } 

		syncRxNotExpectSyncPkt OBJECT-TYPE
		SYNTAX  CounterBasedGauge64 
		MAX-ACCESS read-only 
		STATUS current
		DESCRIPTION  "unexpected session sync packets" 
		::={ acosVrrpAStateS 97 } 

		syncRxExtFwApps OBJECT-TYPE
		SYNTAX  CounterBasedGauge64 
		MAX-ACCESS read-only 
		STATUS current
		DESCRIPTION  "Conn Sync FIREWALL application information Failure" 
		::={ acosVrrpAStateS 98 } 

		syncTxMonEntity OBJECT-TYPE
		SYNTAX  CounterBasedGauge64 
		MAX-ACCESS read-only 
		STATUS current
		DESCRIPTION  "Acos Monitoring Entities Sync Messages Sent" 
		::={ acosVrrpAStateS 99 } 

		syncRxMonEntity OBJECT-TYPE
		SYNTAX  CounterBasedGauge64 
		MAX-ACCESS read-only 
		STATUS current
		DESCRIPTION  "Acos monitoring Entities Sync Messages Received" 
		::={ acosVrrpAStateS 100 } 

		syncRxExtFwGtpLogInfo OBJECT-TYPE
		SYNTAX  CounterBasedGauge64 
		MAX-ACCESS read-only 
		STATUS current
		DESCRIPTION  "FW GTP Log Info Received" 
		::={ acosVrrpAStateS 101 } 

		syncRxDdosDropCounter OBJECT-TYPE
		SYNTAX  CounterBasedGauge64 
		MAX-ACCESS read-only 
		STATUS current
		DESCRIPTION  "Conn Sync receive ddos protect packet" 
		::={ acosVrrpAStateS 102 } 

		syncRxInvalidSyncPacketCounter OBJECT-TYPE
		SYNTAX  CounterBasedGauge64 
		MAX-ACCESS read-only 
		STATUS current
		DESCRIPTION  "Conn Sync receive invalid packet" 
		::={ acosVrrpAStateS 103 } 

		syncRxBadProtocolCounter OBJECT-TYPE
		SYNTAX  CounterBasedGauge64 
		MAX-ACCESS read-only 
		STATUS current
		DESCRIPTION  "Conn Sync receive packet with bad protocol" 
		::={ acosVrrpAStateS 104 } 

		syncRxNoVgrpCounter OBJECT-TYPE
		SYNTAX  CounterBasedGauge64 
		MAX-ACCESS read-only 
		STATUS current
		DESCRIPTION  "Conn Sync receive packet with non-existing group" 
		::={ acosVrrpAStateS 105 } 

		syncRxByInactivePeerCounter OBJECT-TYPE
		SYNTAX  CounterBasedGauge64 
		MAX-ACCESS read-only 
		STATUS current
		DESCRIPTION  "Conn Sync receive packet by inactive peer" 
		::={ acosVrrpAStateS 106 } 

		syncRxSmpCreateCounter OBJECT-TYPE
		SYNTAX  CounterBasedGauge64 
		MAX-ACCESS read-only 
		STATUS current
		DESCRIPTION  "Sync Create SMP Session Pkts Received counter" 
		::={ acosVrrpAStateS 107 } 

		syncRxSmpDeleteCounter OBJECT-TYPE
		SYNTAX  CounterBasedGauge64 
		MAX-ACCESS read-only 
		STATUS current
		DESCRIPTION  "Sync Delete SMP Session Pkts Received counter" 
		::={ acosVrrpAStateS 108 } 

		syncRxSmpUpdateCounter OBJECT-TYPE
		SYNTAX  CounterBasedGauge64 
		MAX-ACCESS read-only 
		STATUS current
		DESCRIPTION  "Sync Update SMP Session Pkts Received counter" 
		::={ acosVrrpAStateS 109 } 

		syncTxSmpCreateCounter OBJECT-TYPE
		SYNTAX  CounterBasedGauge64 
		MAX-ACCESS read-only 
		STATUS current
		DESCRIPTION  "Sync Create SMP Session Pkts Sent counter" 
		::={ acosVrrpAStateS 110 } 

		syncTxSmpDeleteCounter OBJECT-TYPE
		SYNTAX  CounterBasedGauge64 
		MAX-ACCESS read-only 
		STATUS current
		DESCRIPTION  "Sync Delete SMP Session Pkts Sent counter" 
		::={ acosVrrpAStateS 111 } 

		syncTxSmpUpdateCounter OBJECT-TYPE
		SYNTAX  CounterBasedGauge64 
		MAX-ACCESS read-only 
		STATUS current
		DESCRIPTION  "Sync Update SMP Session Pkts Sent counter" 
		::={ acosVrrpAStateS 112 } 

		syncRxSmpClearCounter OBJECT-TYPE
		SYNTAX  CounterBasedGauge64 
		MAX-ACCESS read-only 
		STATUS current
		DESCRIPTION  "Sync Clear SMP Session Pkts Received counter" 
		::={ acosVrrpAStateS 113 } 

		syncTxSmpClearCounter OBJECT-TYPE
		SYNTAX  CounterBasedGauge64 
		MAX-ACCESS read-only 
		STATUS current
		DESCRIPTION  "Sync Clear SMP Session Pkts Sent counter" 
		::={ acosVrrpAStateS 114 } 

acosVrrpACommon                     OBJECT IDENTIFIER ::= { acosVrrpA 3 }
acosVrrpACommonS                    OBJECT IDENTIFIER ::= { acosVrrpACommon 1 }

		vrrpCommonDummy OBJECT-TYPE
		SYNTAX  CounterBasedGauge64 
		MAX-ACCESS read-only 
		STATUS current
		DESCRIPTION  "dummy counter" 
		::={ acosVrrpACommonS 1 } 

acosVrrpAVrid                       OBJECT IDENTIFIER ::= { acosVrrpA 11 }
acosVrrpAVridS                      OBJECT IDENTIFIER ::= { acosVrrpAVrid 1 }

vrrpAVridSTable OBJECT-TYPE
		SYNTAX SEQUENCE OF VrrpAVridSEntry
		MAX-ACCESS not-accessible
		STATUS current
		::={ acosVrrpAVridS 1 } 


	vrrpAVridSEntry OBJECT-TYPE
		SYNTAX VrrpAVridSEntry
		MAX-ACCESS not-accessible
		STATUS current
		INDEX {
			vridVal
		}
		::={ vrrpAVridSTable 1 } 


	VrrpAVridSEntry ::=
		SEQUENCE {
			vridVal INTEGER, 
			associatedVipCount CounterBasedGauge64,
			associatedVportCount CounterBasedGauge64,
			associatedNatpoolCount CounterBasedGauge64
		}

			vridVal OBJECT-TYPE
			SYNTAX  INTEGER 
			MAX-ACCESS read-only 
			STATUS current
			DESCRIPTION  "Specify ha VRRP-A vrid" 
			::={ vrrpAVridSEntry 1 } 

			associatedVipCount OBJECT-TYPE
			SYNTAX  CounterBasedGauge64 
			MAX-ACCESS read-only 
			STATUS current
			DESCRIPTION  "Number of vips associated to vrid" 
			::={ vrrpAVridSEntry 2 } 

			associatedVportCount OBJECT-TYPE
			SYNTAX  CounterBasedGauge64 
			MAX-ACCESS read-only 
			STATUS current
			DESCRIPTION  "Number of vports associated to vrid" 
			::={ vrrpAVridSEntry 3 } 

			associatedNatpoolCount OBJECT-TYPE
			SYNTAX  CounterBasedGauge64 
			MAX-ACCESS read-only 
			STATUS current
			DESCRIPTION  "Number of nat pools associated to vrid" 
			::={ vrrpAVridSEntry 4 } 

END

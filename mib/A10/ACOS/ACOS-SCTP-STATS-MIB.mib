ACOS-SCTP-STATS-MIB DEFINITIONS ::= BEGIN
	IMPORTS
		DisplayString, PhysAddress
		FROM SNMPv2-TC
	InetAddressType
		FROM INET-ADDRESS-MIB
	acosRootStats
		FROM A10-AX-MIB
	MODULE-IDENTITY, OBJECT-TYPE, Counter32, Integer32, Counter64, OBJECT-IDENTITY, NOTIFICATION-TYPE
		FROM SNMPv2-SMI;
		acosSctp MODULE-IDENTITY
				LAST-UPDATED	"200705071327Z"
				ORGANIZATION	"A10 Networks, Inc."
				CONTACT-INFO	"Address: A10 Networks, Inc.
							  3 West Pumeria Dr.
							  San Jose, CA 95131
						 Phone:   +1-888-822-7210 (USA/Canada)
						          +1-408-325-8676 (International)
						 E-mail:  support@A10Networks.com"

				DESCRIPTION	 "Sctp OID for ACOS"
				::=  {  acosRootStats 168  }

acosSctpGlobal                      OBJECT IDENTIFIER ::= { acosSctp 1 }
acosSctpGlobalS                     OBJECT IDENTIFIER ::= { acosSctpGlobal 1 }

		SctpStaticNatSessionCreated OBJECT-TYPE
		SYNTAX  CounterBasedGauge64 
		MAX-ACCESS read-only 
		STATUS current
		DESCRIPTION  "SCTP Static NAT Session Created" 
		::={ acosSctpGlobalS 1 } 

		sctpStaticNatSessionDeleted OBJECT-TYPE
		SYNTAX  CounterBasedGauge64 
		MAX-ACCESS read-only 
		STATUS current
		DESCRIPTION  "SCTP Static NAT Session Deleted" 
		::={ acosSctpGlobalS 2 } 

		SctpFirewallSessionCreated OBJECT-TYPE
		SYNTAX  CounterBasedGauge64 
		MAX-ACCESS read-only 
		STATUS current
		DESCRIPTION  "SCTP Firewall Session Created" 
		::={ acosSctpGlobalS 3 } 

		sctpFwSessionDeleted OBJECT-TYPE
		SYNTAX  CounterBasedGauge64 
		MAX-ACCESS read-only 
		STATUS current
		DESCRIPTION  "SCTP Firewall Session Deleted" 
		::={ acosSctpGlobalS 4 } 

		pktErrDrop OBJECT-TYPE
		SYNTAX  CounterBasedGauge64 
		MAX-ACCESS read-only 
		STATUS current
		DESCRIPTION  "Packet Error Drop" 
		::={ acosSctpGlobalS 5 } 

		badCsum OBJECT-TYPE
		SYNTAX  CounterBasedGauge64 
		MAX-ACCESS read-only 
		STATUS current
		DESCRIPTION  "Bad Checksum" 
		::={ acosSctpGlobalS 6 } 

		badPayloadDrop OBJECT-TYPE
		SYNTAX  CounterBasedGauge64 
		MAX-ACCESS read-only 
		STATUS current
		DESCRIPTION  "Bad Payload Drop" 
		::={ acosSctpGlobalS 7 } 

		badAlignmentDrop OBJECT-TYPE
		SYNTAX  CounterBasedGauge64 
		MAX-ACCESS read-only 
		STATUS current
		DESCRIPTION  "Bad Alignment Drop" 
		::={ acosSctpGlobalS 8 } 

		oosPktDrop OBJECT-TYPE
		SYNTAX  CounterBasedGauge64 
		MAX-ACCESS read-only 
		STATUS current
		DESCRIPTION  "Out-of-state Packet Drop" 
		::={ acosSctpGlobalS 9 } 

		maxMultiHomeDrop OBJECT-TYPE
		SYNTAX  CounterBasedGauge64 
		MAX-ACCESS read-only 
		STATUS current
		DESCRIPTION  "Maximum Multi-homing IP Addresses Drop" 
		::={ acosSctpGlobalS 10 } 

		multiHomeRemoveIpSkip OBJECT-TYPE
		SYNTAX  CounterBasedGauge64 
		MAX-ACCESS read-only 
		STATUS current
		DESCRIPTION  "Multi-homing Remove IP Parameter Skip" 
		::={ acosSctpGlobalS 11 } 

		multiHomeAddrNotFoundDrop OBJECT-TYPE
		SYNTAX  CounterBasedGauge64 
		MAX-ACCESS read-only 
		STATUS current
		DESCRIPTION  "Multi-homing IP Address Not Found Drop" 
		::={ acosSctpGlobalS 12 } 

		staticNatCfgNotFound OBJECT-TYPE
		SYNTAX  CounterBasedGauge64 
		MAX-ACCESS read-only 
		STATUS current
		DESCRIPTION  "Static NAT Config Not Found Drop" 
		::={ acosSctpGlobalS 13 } 

		cfgErrDrop OBJECT-TYPE
		SYNTAX  CounterBasedGauge64 
		MAX-ACCESS read-only 
		STATUS current
		DESCRIPTION  "Configuration Error Drop" 
		::={ acosSctpGlobalS 14 } 

		vrrpStandbyDrop OBJECT-TYPE
		SYNTAX  CounterBasedGauge64 
		MAX-ACCESS read-only 
		STATUS current
		DESCRIPTION  "NAT Resource VRRP-A Standby Drop" 
		::={ acosSctpGlobalS 15 } 

		invalidFragChunkDrop OBJECT-TYPE
		SYNTAX  CounterBasedGauge64 
		MAX-ACCESS read-only 
		STATUS current
		DESCRIPTION  "Invalid Fragmented Chunks Drop" 
		::={ acosSctpGlobalS 16 } 

		disallowedChunkFiltered OBJECT-TYPE
		SYNTAX  CounterBasedGauge64 
		MAX-ACCESS read-only 
		STATUS current
		DESCRIPTION  "Disallowed Chunk Filtered" 
		::={ acosSctpGlobalS 17 } 

		disallowedPktDrop OBJECT-TYPE
		SYNTAX  CounterBasedGauge64 
		MAX-ACCESS read-only 
		STATUS current
		DESCRIPTION  "Disallowed Packet Drop" 
		::={ acosSctpGlobalS 18 } 

		rateLimitDrop OBJECT-TYPE
		SYNTAX  CounterBasedGauge64 
		MAX-ACCESS read-only 
		STATUS current
		DESCRIPTION  "Rate-limit Drop" 
		::={ acosSctpGlobalS 19 } 

		sbySessionCreated OBJECT-TYPE
		SYNTAX  CounterBasedGauge64 
		MAX-ACCESS read-only 
		STATUS current
		DESCRIPTION  "Standby Session Created" 
		::={ acosSctpGlobalS 20 } 

		sbySessionCreateFail OBJECT-TYPE
		SYNTAX  CounterBasedGauge64 
		MAX-ACCESS read-only 
		STATUS current
		DESCRIPTION  "Standby Session Create Failed" 
		::={ acosSctpGlobalS 21 } 

		sbySessionUpdated OBJECT-TYPE
		SYNTAX  CounterBasedGauge64 
		MAX-ACCESS read-only 
		STATUS current
		DESCRIPTION  "Standby Session Updated" 
		::={ acosSctpGlobalS 22 } 

		sbySessionUpdateFail OBJECT-TYPE
		SYNTAX  CounterBasedGauge64 
		MAX-ACCESS read-only 
		STATUS current
		DESCRIPTION  "Standby Session Update Failed" 
		::={ acosSctpGlobalS 23 } 

		sbyStaticNatCfgNotFound OBJECT-TYPE
		SYNTAX  CounterBasedGauge64 
		MAX-ACCESS read-only 
		STATUS current
		DESCRIPTION  "Static NAT Config Not Found on Standby" 
		::={ acosSctpGlobalS 24 } 

		sctpOutOfSystemMemory OBJECT-TYPE
		SYNTAX  CounterBasedGauge64 
		MAX-ACCESS read-only 
		STATUS current
		DESCRIPTION  "Out of System Memory" 
		::={ acosSctpGlobalS 25 } 

		connExtSizeMax OBJECT-TYPE
		SYNTAX  CounterBasedGauge64 
		MAX-ACCESS read-only 
		STATUS current
		DESCRIPTION  "Max Conn Extension Size" 
		::={ acosSctpGlobalS 26 } 

		badCsumShadow OBJECT-TYPE
		SYNTAX  CounterBasedGauge64 
		MAX-ACCESS read-only 
		STATUS current
		DESCRIPTION  "Bad Checksum Shadow" 
		::={ acosSctpGlobalS 27 } 

		badPayloadDropShadow OBJECT-TYPE
		SYNTAX  CounterBasedGauge64 
		MAX-ACCESS read-only 
		STATUS current
		DESCRIPTION  "Bad Packet Payload Drop Shadow" 
		::={ acosSctpGlobalS 28 } 

		badAlignmentDropShadow OBJECT-TYPE
		SYNTAX  CounterBasedGauge64 
		MAX-ACCESS read-only 
		STATUS current
		DESCRIPTION  "Bad Packet Alignment Drop Shadow" 
		::={ acosSctpGlobalS 29 } 

END

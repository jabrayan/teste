ACOS-EVENT-NOTIFICATION-STATS-MIB DEFINITIONS ::= BEGIN
	IMPORTS
		DisplayString, PhysAddress
		FROM SNMPv2-TC
	InetAddressType
		FROM INET-ADDRESS-MIB
	acosRootStats
		FROM A10-AX-MIB
	MODULE-IDENTITY, OBJECT-TYPE, Counter32, Integer32, Counter64, OBJECT-IDENTITY, NOTIFICATION-TYPE
		FROM SNMPv2-SMI;
		acosEventNotification MODULE-IDENTITY
				LAST-UPDATED	"200705071327Z"
				ORGANIZATION	"A10 Networks, Inc."
				CONTACT-INFO	"Address: A10 Networks, Inc.
							  3 West Pumeria Dr.
							  San Jose, CA 95131
						 Phone:   +1-888-822-7210 (USA/Canada)
						          +1-408-325-8676 (International)
						 E-mail:  support@A10Networks.com"

				DESCRIPTION	 "EventNotification OID for ACOS"
				::=  {  acosRootStats 51  }

acosEventNotificationKafka          OBJECT IDENTIFIER ::= { acosEventNotification 1 }
acosEventNotificationKafkaServer    OBJECT IDENTIFIER ::= { acosEventNotificationKafka 1 }
acosEventNotificationKafkaServerS   OBJECT IDENTIFIER ::= { acosEventNotificationKafkaServer 1 }

		prAcosHarmonyTopic OBJECT-TYPE
		SYNTAX  CounterBasedGauge64 
		MAX-ACCESS read-only 
		STATUS current
		DESCRIPTION  "PR topic counter from acos to harmony" 
		::={ acosEventNotificationKafkaServerS 1 } 

		avroDeviceStatusTopic OBJECT-TYPE
		SYNTAX  CounterBasedGauge64 
		MAX-ACCESS read-only 
		STATUS current
		DESCRIPTION  "AVRO device status from acos to harmony" 
		::={ acosEventNotificationKafkaServerS 2 } 

		avroPartitionMetricsTopic OBJECT-TYPE
		SYNTAX  CounterBasedGauge64 
		MAX-ACCESS read-only 
		STATUS current
		DESCRIPTION  "AVRO partition metrics from acos to harmony" 
		::={ acosEventNotificationKafkaServerS 3 } 

		avroGenericSent OBJECT-TYPE
		SYNTAX  CounterBasedGauge64 
		MAX-ACCESS read-only 
		STATUS current
		DESCRIPTION  "Telemetry exported via avro" 
		::={ acosEventNotificationKafkaServerS 4 } 

		prAcosHarmonyTopicEnqueueErr OBJECT-TYPE
		SYNTAX  CounterBasedGauge64 
		MAX-ACCESS read-only 
		STATUS current
		DESCRIPTION  "PR topic to harmony enqueue error" 
		::={ acosEventNotificationKafkaServerS 5 } 

		prAcosHarmonyTopicDequeueErr OBJECT-TYPE
		SYNTAX  CounterBasedGauge64 
		MAX-ACCESS read-only 
		STATUS current
		DESCRIPTION  "PR topic to harmony  dequeue error" 
		::={ acosEventNotificationKafkaServerS 6 } 

		avroGenericFailedEncoding OBJECT-TYPE
		SYNTAX  CounterBasedGauge64 
		MAX-ACCESS read-only 
		STATUS current
		DESCRIPTION  "Telemetry exported via avro failed encoding" 
		::={ acosEventNotificationKafkaServerS 7 } 

		avroGenericFailedSending OBJECT-TYPE
		SYNTAX  CounterBasedGauge64 
		MAX-ACCESS read-only 
		STATUS current
		DESCRIPTION  "Telemetry exported via avro failed sending" 
		::={ acosEventNotificationKafkaServerS 8 } 

		avroDeviceStatusTopicEnqueueErr OBJECT-TYPE
		SYNTAX  CounterBasedGauge64 
		MAX-ACCESS read-only 
		STATUS current
		DESCRIPTION  "AVRO device status enqueue error" 
		::={ acosEventNotificationKafkaServerS 9 } 

		avroDeviceStatusTopicDequeueErr OBJECT-TYPE
		SYNTAX  CounterBasedGauge64 
		MAX-ACCESS read-only 
		STATUS current
		DESCRIPTION  "AVRO device status dequeue error" 
		::={ acosEventNotificationKafkaServerS 10 } 

		avroPartitionMetricsTopicEnqueueErr OBJECT-TYPE
		SYNTAX  CounterBasedGauge64 
		MAX-ACCESS read-only 
		STATUS current
		DESCRIPTION  "Part metrics dropped,enq error on acos queues" 
		::={ acosEventNotificationKafkaServerS 11 } 

		avroPartitionMetricsTopicDequeueErr OBJECT-TYPE
		SYNTAX  CounterBasedGauge64 
		MAX-ACCESS read-only 
		STATUS current
		DESCRIPTION  "Part metrics dropped,enq error analytics queues" 
		::={ acosEventNotificationKafkaServerS 12 } 

		kafkaUnknownTopicDequeueErr OBJECT-TYPE
		SYNTAX  CounterBasedGauge64 
		MAX-ACCESS read-only 
		STATUS current
		DESCRIPTION  "Unknown type dropped,enq error analytics queues" 
		::={ acosEventNotificationKafkaServerS 13 } 

		kafkaBrokerDown OBJECT-TYPE
		SYNTAX  CounterBasedGauge64 
		MAX-ACCESS read-only 
		STATUS current
		DESCRIPTION  "Telemetry drop because kafka broker is down" 
		::={ acosEventNotificationKafkaServerS 14 } 

		kafkaQueueFullErr OBJECT-TYPE
		SYNTAX  CounterBasedGauge64 
		MAX-ACCESS read-only 
		STATUS current
		DESCRIPTION  "Telemetry drop because kafka Queue is full" 
		::={ acosEventNotificationKafkaServerS 15 } 

		prThrottleDrop OBJECT-TYPE
		SYNTAX  CounterBasedGauge64 
		MAX-ACCESS read-only 
		STATUS current
		DESCRIPTION  "L7 PR dropped,log throttling" 
		::={ acosEventNotificationKafkaServerS 16 } 

		prNotAllowedDrop OBJECT-TYPE
		SYNTAX  CounterBasedGauge64 
		MAX-ACCESS read-only 
		STATUS current
		DESCRIPTION  "PR drop because not allowed to log" 
		::={ acosEventNotificationKafkaServerS 17 } 

		prBeTtfbAnomaly OBJECT-TYPE
		SYNTAX  CounterBasedGauge64 
		MAX-ACCESS read-only 
		STATUS current
		DESCRIPTION  "PR back-end ttfb is negative" 
		::={ acosEventNotificationKafkaServerS 18 } 

		prBeTtlbAnomaly OBJECT-TYPE
		SYNTAX  CounterBasedGauge64 
		MAX-ACCESS read-only 
		STATUS current
		DESCRIPTION  "PR back-end ttlb is negative" 
		::={ acosEventNotificationKafkaServerS 19 } 

		prInLatencyThresholdExceed OBJECT-TYPE
		SYNTAX  CounterBasedGauge64 
		MAX-ACCESS read-only 
		STATUS current
		DESCRIPTION  "PR in latency threshold exceeded" 
		::={ acosEventNotificationKafkaServerS 20 } 

		prOutLatencyThresholdExceed OBJECT-TYPE
		SYNTAX  CounterBasedGauge64 
		MAX-ACCESS read-only 
		STATUS current
		DESCRIPTION  "PR out latency threshold exceeded" 
		::={ acosEventNotificationKafkaServerS 21 } 

		prOutLatencyAnomaly OBJECT-TYPE
		SYNTAX  CounterBasedGauge64 
		MAX-ACCESS read-only 
		STATUS current
		DESCRIPTION  "PR out latency negative" 
		::={ acosEventNotificationKafkaServerS 22 } 

		prInLatencyAnomaly OBJECT-TYPE
		SYNTAX  CounterBasedGauge64 
		MAX-ACCESS read-only 
		STATUS current
		DESCRIPTION  "PR in latency negative" 
		::={ acosEventNotificationKafkaServerS 23 } 

		kafkaTopicError OBJECT-TYPE
		SYNTAX  CounterBasedGauge64 
		MAX-ACCESS read-only 
		STATUS current
		DESCRIPTION  "Telemetry dropped because kafka topic not created" 
		::={ acosEventNotificationKafkaServerS 24 } 

		pcEncodingFailed OBJECT-TYPE
		SYNTAX  CounterBasedGauge64 
		MAX-ACCESS read-only 
		STATUS current
		DESCRIPTION  "Telemetry exported via avro failed encoding" 
		::={ acosEventNotificationKafkaServerS 25 } 

		pcAcosHarmonyTopic OBJECT-TYPE
		SYNTAX  CounterBasedGauge64 
		MAX-ACCESS read-only 
		STATUS current
		DESCRIPTION  "PC topic counter from acos to harmony" 
		::={ acosEventNotificationKafkaServerS 26 } 

		pcAcosHarmonyTopicDequeueErr OBJECT-TYPE
		SYNTAX  CounterBasedGauge64 
		MAX-ACCESS read-only 
		STATUS current
		DESCRIPTION  "PC topic to harmony  dequeue error" 
		::={ acosEventNotificationKafkaServerS 27 } 

		cgnPcAcosHarmonyTopic OBJECT-TYPE
		SYNTAX  CounterBasedGauge64 
		MAX-ACCESS read-only 
		STATUS current
		DESCRIPTION  "CGN PC topic counter from acos to harmony" 
		::={ acosEventNotificationKafkaServerS 28 } 

		cgnPcAcosHarmonyTopicDequeueErr OBJECT-TYPE
		SYNTAX  CounterBasedGauge64 
		MAX-ACCESS read-only 
		STATUS current
		DESCRIPTION  "CGN PC topic to harmony dequeue error" 
		::={ acosEventNotificationKafkaServerS 29 } 

		cgnPeAcosHarmonyTopic OBJECT-TYPE
		SYNTAX  CounterBasedGauge64 
		MAX-ACCESS read-only 
		STATUS current
		DESCRIPTION  "CGN PE topic counter from acos to harmony" 
		::={ acosEventNotificationKafkaServerS 30 } 

		cgnPeAcosHarmonyTopicDequeueErr OBJECT-TYPE
		SYNTAX  CounterBasedGauge64 
		MAX-ACCESS read-only 
		STATUS current
		DESCRIPTION  "CGN PE topic to harmony dequeue error" 
		::={ acosEventNotificationKafkaServerS 31 } 

		fwPcAcosHarmonyTopic OBJECT-TYPE
		SYNTAX  CounterBasedGauge64 
		MAX-ACCESS read-only 
		STATUS current
		DESCRIPTION  "FW PC topic counter from acos to harmony" 
		::={ acosEventNotificationKafkaServerS 32 } 

		fwPcAcosHarmonyTopicDequeueErr OBJECT-TYPE
		SYNTAX  CounterBasedGauge64 
		MAX-ACCESS read-only 
		STATUS current
		DESCRIPTION  "FW PC topic to harmony dequeue error" 
		::={ acosEventNotificationKafkaServerS 33 } 

		fwDenyPcAcosHarmonyTopic OBJECT-TYPE
		SYNTAX  CounterBasedGauge64 
		MAX-ACCESS read-only 
		STATUS current
		DESCRIPTION  "FW DENY PC topic counter from acos to harmony" 
		::={ acosEventNotificationKafkaServerS 34 } 

		fwDenyPcAcosHarmonyTopicDequeueErr OBJECT-TYPE
		SYNTAX  CounterBasedGauge64 
		MAX-ACCESS read-only 
		STATUS current
		DESCRIPTION  "FW DENY PC logs dropped,enq error analytics queues" 
		::={ acosEventNotificationKafkaServerS 35 } 

		fwRstPcAcosHarmonyTopic OBJECT-TYPE
		SYNTAX  CounterBasedGauge64 
		MAX-ACCESS read-only 
		STATUS current
		DESCRIPTION  "FW RST PC topic counter from acos to harmony" 
		::={ acosEventNotificationKafkaServerS 36 } 

		fwRstPcAcosHarmonyTopicDequeueErr OBJECT-TYPE
		SYNTAX  CounterBasedGauge64 
		MAX-ACCESS read-only 
		STATUS current
		DESCRIPTION  "FW RST PC topic to harmony dequeue error" 
		::={ acosEventNotificationKafkaServerS 37 } 

		cgnSummaryErrorAcosHarmonyTopic OBJECT-TYPE
		SYNTAX  CounterBasedGauge64 
		MAX-ACCESS read-only 
		STATUS current
		DESCRIPTION  "CGN Summary PE topic counter from acos to harmony" 
		::={ acosEventNotificationKafkaServerS 38 } 

		cgnSummaryErrorAcosHarmonyTopicDequeueErr OBJECT-TYPE
		SYNTAX  CounterBasedGauge64 
		MAX-ACCESS read-only 
		STATUS current
		DESCRIPTION  "CGN Summary PE topic to harmony dequeue error" 
		::={ acosEventNotificationKafkaServerS 39 } 

		ruleSetApplicationMetricsTopic OBJECT-TYPE
		SYNTAX  CounterBasedGauge64 
		MAX-ACCESS read-only 
		STATUS current
		DESCRIPTION  "AppFW metrics from acos to harmony" 
		::={ acosEventNotificationKafkaServerS 40 } 

		ruleSetApplicationMetricsTopicDequeueErr OBJECT-TYPE
		SYNTAX  CounterBasedGauge64 
		MAX-ACCESS read-only 
		STATUS current
		DESCRIPTION  "AppFW metrics dequeue error" 
		::={ acosEventNotificationKafkaServerS 41 } 

		slbSslStatsMetricsTopic OBJECT-TYPE
		SYNTAX  CounterBasedGauge64 
		MAX-ACCESS read-only 
		STATUS current
		DESCRIPTION  "SSL stats metrics from acos to harmony" 
		::={ acosEventNotificationKafkaServerS 42 } 

		slbSslStatsMetricsTopicDequeueErr OBJECT-TYPE
		SYNTAX  CounterBasedGauge64 
		MAX-ACCESS read-only 
		STATUS current
		DESCRIPTION  "SSL stats metrics dequeue error" 
		::={ acosEventNotificationKafkaServerS 43 } 

		slbClientSslCountersMetricsTopic OBJECT-TYPE
		SYNTAX  CounterBasedGauge64 
		MAX-ACCESS read-only 
		STATUS current
		DESCRIPTION  "Client SSL counters metrics from acos to harmony" 
		::={ acosEventNotificationKafkaServerS 44 } 

		slbClientSslCountersMetricsTopicDequeueErr OBJECT-TYPE
		SYNTAX  CounterBasedGauge64 
		MAX-ACCESS read-only 
		STATUS current
		DESCRIPTION  "Cilent SSL metrics dropped,enq error analytics qs" 
		::={ acosEventNotificationKafkaServerS 45 } 

		slbServerSslCountersMetricsTopic OBJECT-TYPE
		SYNTAX  CounterBasedGauge64 
		MAX-ACCESS read-only 
		STATUS current
		DESCRIPTION  "Server SSL counters metrics from acos to harmony" 
		::={ acosEventNotificationKafkaServerS 46 } 

		slbServerSslCountersMetricsTopicDequeueErr OBJECT-TYPE
		SYNTAX  CounterBasedGauge64 
		MAX-ACCESS read-only 
		STATUS current
		DESCRIPTION  "Server SSL metrics dropped,enq error analytics qs" 
		::={ acosEventNotificationKafkaServerS 47 } 

		pcThrottleDrop OBJECT-TYPE
		SYNTAX  CounterBasedGauge64 
		MAX-ACCESS read-only 
		STATUS current
		DESCRIPTION  "PC drop due to throttling" 
		::={ acosEventNotificationKafkaServerS 48 } 

		metricsDroppedPtMissing OBJECT-TYPE
		SYNTAX  CounterBasedGauge64 
		MAX-ACCESS read-only 
		STATUS current
		DESCRIPTION  "Partition-Tenant mapping not saved on HC" 
		::={ acosEventNotificationKafkaServerS 49 } 

		ssliPcAcosHarmonyTopic OBJECT-TYPE
		SYNTAX  CounterBasedGauge64 
		MAX-ACCESS read-only 
		STATUS current
		DESCRIPTION  "SSLi PC topic counter from acos to harmony" 
		::={ acosEventNotificationKafkaServerS 50 } 

		ssliPcAcosHarmonyTopicDequeueErr OBJECT-TYPE
		SYNTAX  CounterBasedGauge64 
		MAX-ACCESS read-only 
		STATUS current
		DESCRIPTION  "SSLi PC topic to harmony dequeue error" 
		::={ acosEventNotificationKafkaServerS 51 } 

		ssliPeAcosHarmonyTopic OBJECT-TYPE
		SYNTAX  CounterBasedGauge64 
		MAX-ACCESS read-only 
		STATUS current
		DESCRIPTION  "SSLi PE topic counter from acos to harmony" 
		::={ acosEventNotificationKafkaServerS 52 } 

		ssliPeAcosHarmonyTopicDequeueErr OBJECT-TYPE
		SYNTAX  CounterBasedGauge64 
		MAX-ACCESS read-only 
		STATUS current
		DESCRIPTION  "SSLi PE topic to harmony dequeue error" 
		::={ acosEventNotificationKafkaServerS 53 } 

		analyticsBusRestart OBJECT-TYPE
		SYNTAX  CounterBasedGauge64 
		MAX-ACCESS read-only 
		STATUS current
		DESCRIPTION  "Analytics bus restart count" 
		::={ acosEventNotificationKafkaServerS 54 } 

END
